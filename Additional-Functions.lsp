; ---Additional Functions---
; Written by David Lane-Smith
; To optimize use of AutoCAD at Ecoland Inc.



; Reads the save file and sets variables to their saved values upon loading program

(load "C:\\Users\\Ecoland\\Documents\\Helpful Code\\LSP Files\\Preset.lsp")
(setq saveF (open "C:\\Users\\Ecoland\\Documents\\Helpful Code\\LSP Files\\SaveFile.txt" "r"))
(setq lin (read-line savef))
(if (= lin nil) (setq num 1) (setq num (atof lin)))
(setq lin (read-line savef))
(if (= lin nil) (setq textH 1) (setq textH (atof lin)))
(setq lin (read-line savef))
(setq lin (read-line savef))
(if (= lin nil) (setq cur_oVal (getvar "osmode")) (setq cur_oVal (atoi lin)))
(setq lin (read-line savef))
(if (= lin nil)
	(progn
		(setq dPntOn T)
	)
	(progn
		(setq dPntOn (atoi lin))
	)
)
(setq lin (read-line savef))
(if (= lin nil)
	(progn
		(setq dLblOn T)
	)
	(progn
		(setq dLblOn (atoi lin))
	)
)
(setq lin (read-line savef))
(if (= lin nil)
	(progn
		(setq dBoxOn T)
	)
	(progn
		(setq dBoxOn (atoi lin))
	)
)
(setq lin (read-line savef))
(if (= lin nil)
	(progn
		(setq dCoordOn T)
	)
	(progn
		(setq dCoordOn (atoi lin))
	)
)
(setq lin (read-line savef))
(if (= lin nil)
	(progn
		(setq dCLbl T)
	)
	(progn
		(setq dCLbl (atoi lin))
	)
)
(setq lin (read-line savef))
(if (= lin nil)
	(progn
		(setq elOn 1)
	)
	(progn
		(setq elOn (atoi lin))
	)
)
(setq lin (read-line savef))
(if (= lin nil)
	(progn
		(setq arrow 1)
	)
	(progn
		(setq arrow (atoi lin))
	)
)
(setq lin (read-line savef))
(if (= lin nil)
	(progn
		(setq prntCrd 1)
	)
	(progn
		(setq prntCrd (atoi lin))
	)
)
(setq
	PntOn dPntOn
	LblOn dLblOn
	BoxOn dBoxOn
	CoordOn dCoordOn
	CLbl dCLbl
)
(close saveF)
(setq textAR (- (* PI 2) (getvar "viewtwist")))
(setq textA (* textAR (/ 180 PI)))
(setq norm 1)
(setq sNum nil)

(defun c:cur( / num msg) ; Sets OSNAP mode to the standard as dictated by the save file
	(setvar "osmode" cur_oVal)
	(setq num (itoa cur_oVal))
	(setq msg (strcat "OSMODE set to " num))
	(princ msg)
	(princ)
) ; defun

(defun c:cir() ; Sets OSNAP mode to just node and circle, for selecting circles
	(setq cur_oVal (getvar "osmode"))
	(setvar "osmode" 12)
	(princ "OSMODE set to 12")
	(princ)
) ; defun

(defun c:recur() ; Sets saved OSNAP mode to the current mode
	(setq cur_oVal (getvar "osmode"))
	(writeToSaveFile (binMode (list 4)) (list (rtos cur_oVal)))
	(princ)
) ; defun

(defun c:defpt()
	(PntNLbl dPntOn dLblOn dBoxOn dCoordOn dCLbl)
	(princ)
)

(defun c:pt()
	(PntNLbl PntOn LblOn BoxOn CoordOn CLbl)
	(princ)
)

; Places point and records coordinate in file, labels the point and repeats with the label increasing by 1
; Different modes affect which capabilites are enabled

(defun PntNLbl(m1 m2 m3 m4 m5 / lp2 xc yc pntm1 pntm2 cnt e outN outF saveF lin coordF ch lp em pnt1 pnt2 pntb pntf a b dis x y linN ss numStr wrt os num rAng fP fN i filP chk unN boxE temp tempI smP ptS pntName boxName txtName arrName)
	(setq lp 1)
	(setq lp2 1)
	(setq em 0)
	(setq chk 1)
	(setq skip 0)
	(regapp "Name")
	(setq coordF (open "C:\\Users\\Ecoland\\Documents\\Helpful Code\\LSP Files\\CoordFile.txt" "w"))
	(setq ch (findfile "C:\\Users\\Ecoland\\Documents\\Helpful Code\\LSP Files\\SaveFile.txt"))
	(if (= ch nil)
		(setq num (getint "\nEnter the first number: "))
		(progn
			(setq saveF (open "C:\\Users\\Ecoland\\Documents\\Helpful Code\\LSP Files\\SaveFile.txt" "r"))
			(setq lin (read-line savef))
			(close saveF)
			(if (= lin nil)
				(progn
					(setq num (vl-catch-all-apply 'getint (list "Enter the first number: ")))
					(if (vl-catch-all-error-p num)
						(if (equal (vl-catch-all-error-message b) "Function cancelled")
							(setq lp 0)
							(progn
								(prompt (strcat "\nError: " (vl-catch-all-error-message b) ". First number set to 1."))
								(setq num 1)
							)
						)
					)
				)
				(progn
					(setq linN (atoi lin))
					(setq num linN)
				) ; progn
			) ; if
			(if (= sNum num)
				(setq skip 1)
				(progn
					(setq fP "C:\\Users\\Ecoland\\Documents\\Point Drawings\\Points\\Deleted Points\\")
					(setq fN (getvar "dwgname"))
					(setq i 1)
					(while (not (= (substr fN i 1) ".")) (setq i (1+ i)))
					(setq fN (substr fN 1 (- i 1)))
					(setq fP (strcat fP fN "-deleted points.txt"))
				)
			)
		) ; progn
	) ; if
	(if (= lp 1)
		(progn
			(setq numStr (itoa num))
			(setq outN (itoa m5))
			(setq outF (getvar "dwgname"))
			(write-line outN coordF)
			(write-line outF coordF)
			(write-line "" coordF)
			(if (not bns_tcircle) (load "acettxt.lsp"))
		)
	)
	(while (and (= lp 1) (= lp2 1))
		(setq unN 0)
		(setq txtName nil)
		(setq boxName nil)
		(if (or (= m1 1) (= m4 1))
			(progn
				(if (> (getvar "osmode") 16383) (setvar "osmode" (- (getvar "osmode") 16384)))
				(setq pnt1 (vl-catch-all-apply 'getpoint (list "\nChoose point: ")))
				(if (vl-catch-all-error-p pnt1)
					(progn
						(if (equal (vl-catch-all-error-message pnt1) "Function cancelled") ()
							(progn
								(prompt (strcat "\nError: " (vl-catch-all-error-message pnt1) "."))
								(setq em 2)
							)
						)
						(setq lp 0)
					)
					(progn
						(if (= m1 1) (progn (command "._point" pnt1) (setq pntName (entlast)) (setq unN (1+ unN))) (setq pntName nil))
						(if (= m4 1)
							(progn
								(setq x (rtos (car pnt1) 2 5))
								(setq y (rtos (cadr pnt1) 2 5))
								(setq z (rtos (caddr pnt1) 2 5))
							) ; progn
						) ; if
					) ; progn
				) ; if
			) ; progn
		) ; if
		(if (= lp 1)
			(progn
				(if (< (getvar "osmode") 16384) 
					(progn
						(setq os 1)
						(setvar "osmode" (+ (getvar "osmode") 16384))
					)
					(setq os 0)
				)
				(if (and (= skip 0) (= chk 1))
					(if (> (vl-file-size fP) 0)
						(progn
							(setq delF (open fP "r"))
							(setq lin (read-line delF))
							(setq numStr lin)
							(setq num (atoi numStr))
							(setq lst '())
							(while (not (= (setq lin (read-line delF)) nil))
								(setq lst (append lst (list lin)))
							)
							(close delF)
							(setq delF (open fP "w"))
							(while (not (= (car lst) nil))
								(write-line (car lst) delF)
								(setq lst (cdr lst))
							)
							(close delF)
						)
						(progn
							(setq p nil)
							(setq filP (strcat "C:\\Users\\Ecoland\\Documents\\Point Drawings\\Points\\" fN "-points.txt"))
							(if (findfile filP)
								(progn
									(setq lasF (open filP "r"))
									(while (not (= (setq lin (read-line lasF)) nil))
										(setq p lin)
									)
									(close lasF)
								)
							)
							(if (not p)
								(setq num 1)
								(progn
									(setq i 1)
									(while (not (= (substr p i 1) ",")) (setq i (1+ i)))
									(setq numStr (substr p 1 (- i 1)))
									(setq num (+ (atoi numStr) 1))
								)
							)
							(setq numStr (itoa num))
							(setq chk 0)
						)
					)	
				)
				(if (= m5 1)
					(progn
						(setq numStr (vl-catch-all-apply 'getstring (list "\nInput label: ")))
						(if (vl-catch-all-error-p numStr)
							(progn
								(if (equal (vl-catch-all-error-message numStr) "Function cancelled")
									()
									(progn
										(prompt (strcat "\nError: " (vl-catch-all-error-message numStr) "."))
										(setq em 2)
									)
								)
								(setq lp 0)
							)
						)
					)
				)
				(if (= lp 1)
					(progn
						(if (= m4 1) 
							(progn
								(setq wrt (strcat numStr "," x "," y))
								(if (= elOn 1) (setq wrt (strcat wrt "," z)))
							)
						)
						(if (or (= m1 1) (= m4 1))
							(setq pnt2 pnt1)
							(progn
								(setq pnt2 (getCursor))
							)
						)
					)
				)
				(if (and (= lp 1) (= m2 1))
					(progn
						(setq ptS (* (getvar "PDSIZE") 0.73))
						(setq xl (/ (* textH 0.36) (getvar "cannoscalevalue")))
						(setq yl (/ (* textH 0.5) (getvar "cannoscalevalue")))
						(setq xt (+ ptS xl))
						(setq yt (+ ptS yl))
						(setq dis (sqrt (+ (expt xt 2) (expt yt 2))))
						(setq rAng (getvar "viewtwist"))
						(setq tAng (- (atan yt xt) rAng))
						(setq a (* dis (cos tAng)))
						(setq b (* dis (sin tAng)))
						(setq pntf (list (+ (car pnt2) a) (+ (cadr pnt2) b)))
						(if (= prntCrd 0)
							(command "._text" pntf textH textA numStr)
							(progn
								(setq Spntf (strcat (rtos (car pntf) 2 3) "," (rtos (cadr pntf) 2 3) ",0"))
								(command "._mtext" Spntf "r" textA "h" textH "w" 20 (strcat "Name: " numStr "\nN: " (rtos (cadr pnt2) 2 3) "\nE: " (rtos (car pnt2) 2 3) "\nEl: " (rtos (caddr pnt2) 2 3)) "")
							)
						)
						(setq unN (+ unN 2))
						(setq txtName (entlast))
						(setq ss (ssget "_L"))
						(setq smP nil)
						(if (= m3 1)
							(progn
								(bns_tcircle ss "Variable" "Rectangles" nil 0.35)
								(setq boxName (entlast))
								(setq ss (ssadd (entlast) ss))
								
								(setq boxE (entget boxName))
								(while (not (not boxE))
									(setq tempI (car boxE))
									(if (= (car tempI) 10)
										(progn
											(setq temp (cdr tempI))
											(if (not smP)
												(setq smP temp)
												(progn
													(if (< (distance temp pnt2) (distance smP pnt2))
														(setq smP temp)
													)
												)
											)
										)
									)
									(setq boxE (cdr boxE))
								)
							) ; progn
							(setq smP (cdr (assoc 10 (entget txtName))))
						) ; if
						(repeat (setq cnt (sslength ss))
							(setq e (ssname ss (setq cnt (1- cnt))))
							(if (or (= (cdr (assoc 0 (entget e))) "TEXT") (= (cdr (assoc 0 (entget e))) "MTEXT"))
								(progn
									(setq xc (cadr (assoc 10 (entget e))))
									(setq yc (caddr (assoc 10 (entget e))))
									(setq pntm1 (list xc yc))
								)
							)
						)
						(setq err (vl-catch-all-apply 'moveL (list ss smP)))
						(repeat (setq cnt (sslength ss))
							(setq e (ssname ss (setq cnt (1- cnt))))
							(if (or (= (cdr (assoc 0 (entget e))) "TEXT") (= (cdr (assoc 0 (entget e))) "MTEXT"))
								(progn
									(setq xc (cadr (assoc 10 (entget e))))
									(setq yc (caddr (assoc 10 (entget e))))
									(setq pntm2 (list xc yc))
								)
							)
						)
						(if (equal pntm1 pntm2)
							(progn
								(setq em 1)
								(setq lp 0)
							)
						)
						(if (vl-catch-all-error-p err)
							(progn
								(prompt (strcat "\nError: " (vl-catch-all-error-message err) "."))
								(setq em 2)
								(setq lp 0)
							)
						)
						(if (and (= lp 1) (and (= arrow 1) (or (= m1 1) (= m4 1))))
							(progn
								(setq smP nil)
								(if (= m3 1)
									(progn
										(setq boxE (entget boxName))
										(while (not (not boxE))
											(setq tempI (car boxE))
											(if (= (car tempI) 10)
												(progn
													(setq temp (cdr tempI))
													(if (not smP)
														(setq smP temp)
														(if (< (distance temp pnt2) (distance smP pnt2))
															(setq smP temp)
														)
													)
												)
											)
											(setq boxE (cdr boxE))
										)
									) ; progn
									(progn
										(setq txtC (cdr (assoc 10 (entget txtName))))
										(setq txtA (cdr (assoc 50 (entget txtName))))
										(setq ptR (textbox (entget txtName)))
										(setq pt1R (car ptR))
										(setq pt2R (cadr ptR))
										(setq x1 (* (car pt1R) (cos txtA)))
										(setq x1 (+ x1 (* (cadr pt1R) (cos (+ txtA (/ PI 2))))))
										(setq y1 (* (car pt1R) (sin txtA)))
										(setq y1 (+ y1 (* (cadr pt1R) (sin (+ txtA (/ PI 2))))))
										(setq pt1A (list (+ (car txtC) x1) (+ (cadr txtC) y1)))
										
										(setq x2 (* (car pt2R) (cos txtA)))
										(setq x2 (+ x2 (* (cadr pt2R) (cos (+ txtA (/ PI 2))))))
										(setq y2 (* (car pt2R) (sin txtA)))
										(setq y2 (+ y2 (* (cadr pt2R) (sin (+ txtA (/ PI 2))))))
										(setq pt2A (list (+ (car txtC) x2) (+ (cadr txtC) y2)))
										
										(setq x3 (* (car pt1R) (cos txtA)))
										(setq x3 (+ x3 (* (cadr pt2R) (cos (+ txtA (/ PI 2))))))
										(setq y3 (* (car pt1R) (sin txtA)))
										(setq y3 (+ y3 (* (cadr pt2R) (sin (+ txtA (/ PI 2))))))
										(setq pt3A (list (+ (car txtC) x3) (+ (cadr txtC) y3)))
										
										(setq x4 (* (car pt2R) (cos txtA)))
										(setq x4 (+ x4 (* (cadr pt1R) (cos (+ txtA (/ PI 2))))))
										(setq y4 (* (car pt2R) (sin txtA)))
										(setq y4 (+ y4 (* (cadr pt1R) (sin (+ txtA (/ PI 2))))))
										(setq pt4A (list (+ (car txtC) x4) (+ (cadr txtC) y4)))
										
										(setq ptAL (list pt1A pt2A pt3A pt4A))
										(while (/= (setq temp (car ptAL)) nil)
											(if (not smP)
												(setq smP temp)
												(if (< (distance temp pnt2) (distance smP pnt2))
													(setq smP temp)
												)
											)
											(setq ptAL (cdr ptAL))
										)
									)
								) ; if
								(setq arLW (/ (/ textH 2) (getvar "cannoscalevalue")))
								(setq arA (atan (- (cadr smP) (cadr pnt2)) (- (car smP) (car pnt2))))
								(if (< (distance smP pnt2) (/ textH (getvar "cannoscalevalue")))
									(setq arLW (/ (distance smP pnt2) 2))
								)
								(command "_pline" pnt2 "w" 0  arLW (setq p (polar pnt2 arA arLW)) "w" 0 0 (polar p arA (- (distance smP pnt2) arLW)) "")
								(setq arrName (entlast))
							)
						)
					)
				)
				(if (and (= lp 1) (and (= m5 0) (= m4 1)))
					(progn
						(if (not (= pntName nil))
							(progn
								(setq lastent (entget pntName))
								(setq exdata (list (list -3 (list "Name" (cons 1000 numStr)))))
								(setq lastent (append lastent exdata))
								(entmod lastent)
							)
						)
						(if (not (= txtName nil))
							(progn
								(setq lastent (entget txtName))
								(setq exdata (list (list -3 (list "Name" (cons 1000 numStr)))))
								(setq lastent (append lastent exdata))
								(entmod lastent)
							)
						)
						(if (not (= boxName nil))
							(progn
								(setq lastent (entget boxName))
								(setq exdata (list (list -3 (list "Name" (cons 1000 numStr)))))
								(setq lastent (append lastent exdata))
								(entmod lastent)
							)
						)
						(if (not (= arrName nil))
							(progn
								(setq lastent (entget arrName))
								(setq exdata (list (list -3 (list "Name" (cons 1000 numStr)))))
								(setq lastent (append lastent exdata))
								(entmod lastent)
							)
						)
					)
				)
				(if (and (= os 1) (> (getvar "osmode") 16383)) (setvar "osmode" (- (getvar "osmode") 16384)))
			) ; progn
		) ; if
		(if (and (= m5 0) (= lp 1))
			(progn
				(setq num (1+ num))
				(setq numStr (itoa num))
				(writeToSaveFile (binMode (list 1)) (list numStr))
			)
		)
		(if (and (= m4 1) (= lp 1)) (write-line wrt coordF))
		(if (= norm 0) (setq lp2 0))
	) ; while
	(if (= norm 1) (HandErr em (= m1 1) (= m2 1) (= m4 1) unN))
	(close coordF)
	(princ)
)

(defun moveL(sel pntb)
	(command "._move" sel "" pntb pause)
	(princ)
)

(defun HandErr(em m1 m2 m4 unN / q loop)
	(if (not (= unN 0))
		(command "._undo" unN)
	)
	(if m4
		(progn
			(setq loop T)
			(while loop
				(setq q (getYN "Save to File [Yes/No] <Yes>: "))
				(if (= q 1)
					(progn
						(writeToCModes (binMode (list 1)) (list "0"))
						(startapp "C:\\Users\\Ecoland\\Documents\\Helpful Code\\Coordinate Formatter.exe")
						(prompt "\nCoordinates saved to file.")
						(setq loop nil)
					)
					(progn
						(if (= q 0)
							(setq loop nil)
							(progn
								(prompt "\nInvalid input!\n")
							)
						)
					)
				)
			)
		)
	)
	(if (= em 2)
		(prompt "\nFunction terminated improperly.")
	)
)

(defun getYN(pr / inS loop)
	(setq loop T)
	(while loop
		(initget "Y N")
		(setq inS (cond ((getkword pr)) ("Y")))
		(if (= inS "Y") (progn (setq loop nil) 1) 
			(progn
				(if (= ins "N") (progn (setq loop nil) 0)
					(progn
						(prompt "\nInvalid input. Try again.\n")
					)
				)
			)
		)
	)
)

(defun c:test()
	(c:setnum)
	(princ)
)

(defun test2(a)
	(setq b (vl-catch-all-apply 'getpoint (list "Input num: ")))
	(if (vl-catch-all-error-p b)
		(progn
			(if (equal (vl-catch-all-error-message b) "Function cancelled")
				(print "esc pressed in 2")
				(print (strcat "not esc2: " (vl-catch-all-error-message b)))
			)
			(setq b 2)
		)
	)
	(/ a b)
)

(defun c:setNum( / numStr num) ; Sets new starting number for label, and saves it to the save file
	(setq num (getint "\nEnter new starting number: "))
	(setq numStr (rtos num))
	(setq sNum num)
	(writeToSaveFile (binMode (list 1)) (list numStr))
	(princ)
) ; defun

(defun c:setText() ; Sets new height and angle of text, and saves it to the save file
	(c:setHeight)
	(c:setAngle)
	(princ)
) ; defun

(defun c:setHeight( / textHStr)
	(setq textH (getdist (getCursor) "\nSelect height of text: "))
	(setq textHStr (rtos textH 2 3))
	(prompt (strcat "\nText height: " textHStr))
	(writeToSaveFile (binMode (list 2)) (list textHStr))
	(princ)
)

(defun getCursor( / a b c tpnt pnt)
	(setq
		c (grread T)
		tpnt (cadr c)
		a (car tpnt)
		b (cadr tpnt)
		pnt (list a b)
	)
)

(defun c:setAngle( / ang textAStr)
	(setq ang (getorient (getCursor) "\nDraw a horizontal line: "))
	(setq textA (* ang (/ 180 PI)))
	(setq textAStr (rtos textA 2 2))
	(prompt (strcat "\nText angle: " textAStr " degrees"))
	(writeToSaveFile (binMode (list 3)) (list textAStr))
	(princ)
)

(defun writeToSaveFile (mod outL / strt textH textA cur_oVal fPnt fLbl fBox fCoord fCLbl elOn arrow prntCrd)
	(setq mLst (binToLst mod))
	(setq saveF (open "C:\\Users\\Ecoland\\Documents\\Helpful Code\\LSP Files\\SaveFile.txt" "r"))
	(setq i 1)
	(setq lin (read-line saveF))
		(if (= (cdr (assoc 1 mLst)) 1)
			(progn
				(setq strt (car outL))
				(setq outL (cdr outL))
			)
			(setq strt lin)
		)
	(setq lin (read-line saveF))
	(if (= (cdr (assoc 2 mLst)) 1)
		(progn
			(setq textH (car outL))
			(setq outL (cdr outL))
		)
		(setq textH lin)
	)
	(setq lin (read-line saveF))
	(if (= (cdr (assoc 3 mLst)) 1)
		(progn
			(setq textA (car outL))
			(setq outL (cdr outL))
		)
		(setq textA lin)
	)
	(setq lin (read-line saveF))
	(if (= (cdr (assoc 4 mLst)) 1)
		(progn
			(setq cur_oVal (car outL))
			(setq outL (cdr outL))
		)
		(setq cur_oVal lin)
	)
	(setq lin (read-line saveF))
	(if (= (cdr (assoc 5 mLst)) 1)
		(progn
			(setq fPnt (car outL))
			(setq outL (cdr outL))
		)
		(setq fPnt lin)
	)
	(setq lin (read-line saveF))
	(if (= (cdr (assoc 6 mLst)) 1)
		(progn
			(setq fLbl (car outL))
			(setq outL (cdr outL))
		)
		(setq fLbl lin)
	)
	(setq lin (read-line saveF))
	(if (= (cdr (assoc 7 mLst)) 1)
		(progn
			(setq fBox (car outL))
			(setq outL (cdr outL))
		)
		(setq fBox lin)
	)
	(setq lin (read-line saveF))
	(if (= (cdr (assoc 8 mLst)) 1)
		(progn
			(setq fCoord (car outL))
			(setq outL (cdr outL))
		)
		(setq fCoord lin)
	)
	(setq lin (read-line saveF))
	(if (= (cdr (assoc 9 mLst)) 1)
		(progn
			(setq fCLbl (car outL))
			(setq outL (cdr outL))
		)
		(setq fCLbl lin)
	)
	(setq lin (read-line saveF))
	(if (= (cdr (assoc 10 mLst)) 1)
		(progn
			(setq elOn (car outL))
			(setq outL (cdr outL))
		)
		(setq elOn lin)
	)
	(setq lin (read-line saveF))
	(if (= (cdr (assoc 11 mLst)) 1)
		(progn
			(setq arrow (car outL))
			(setq outL (cdr outL))
		)
		(setq arrow lin)
	)
	(setq lin (read-line saveF))
	(if (= (cdr (assoc 12 mLst)) 1)
		(progn
			(setq prntCrd (car outL))
			(setq outL (cdr outL))
		)
		(setq prntCrd lin)
	)
	(close saveF)
	(setq saveF (open "C:\\Users\\Ecoland\\Documents\\Helpful Code\\LSP Files\\SaveFile.txt" "w"))
	(if (not strt) (write-line "NULL" saveF) (write-line strt saveF))
	(if (not textH) (write-line "NULL" saveF) (write-line textH saveF))
	(if (not textA) (write-line "NULL" saveF) (write-line textA saveF))
	(if (not cur_oVal) (write-line "NULL" saveF) (write-line cur_oVal saveF))
	(if (not fPnt) (write-line "NULL" saveF) (write-line fPnt saveF))
	(if (not fLbl) (write-line "NULL" saveF) (write-line fLbl saveF))
	(if (not fBox) (write-line "NULL" saveF) (write-line fBox saveF))
	(if (not fCoord) (write-line "NULL" saveF) (write-line fCoord saveF))
	(if (not fCLbl) (write-line "NULL" saveF) (write-line fCLbl saveF))
	(if (not elOn) (write-line "NULL" saveF) (write-line elOn saveF))
	(if (not arrow) (write-line "NULL" saveF) (write-line arrow saveF))
	(if (not prntCrd) (write-line "NULL" saveF) (write-line prntCrd saveF))
	(close saveF)
	(princ)
)

(defun binToLst(bin)
	(setq mLst '())
	(setq i 1)
	(while (>= bin i)
		(setq i (* i 2))
	)
	(setq i (/ i 2))
	(while (>= i 1)
		(setq li (+ (/ (log i) (log 2)) 1))
		(setq j i)
		(setq i (/ i 2))
		(if (>= bin j)
			(progn
				(setq bin (- bin j))
				(setq mLst (cons (cons li 1) mLst))
			)
			(setq mLst (cons (cons li 0) mLst))
		)
	)
)

(defun writeToCModes(mod outL / i li mLst ln1 ln2 ln3 lin)
	(setq mLst (binToLst mod))
	(setq cMode (open "C:\\Users\\Ecoland\\Documents\\Helpful Code\\cModes.txt" "r"))
	(setq lin (read-line cMode))
	(if (= (cdr (assoc 1 mLst)) 1)
		(progn
			(setq ln1 (car outL))
			(setq outL (cdr outL))
		)
		(setq ln1 lin)
	)
	(setq lin (read-line cMode))
	(if (= (cdr (assoc 2 mLst)) 1)
		(progn
			(setq ln2 (car outL))
			(setq outL (cdr outL))
		)
		(setq ln2 lin)
	)
	(setq lin (read-line cMode))
	(if (= (cdr (assoc 3 mLst)) 1)
		(progn
			(setq ln3 (car outL))
			(setq outL (cdr outL))
		)
		(setq ln3 lin)
	)
	(close cMode)
	(setq cMode (open "C:\\Users\\Ecoland\\Documents\\Helpful Code\\cModes.txt" "w"))
	(if (not ln1) (write-line "NULL" cMode) (write-line ln1 cMode))
	(if (not ln2) (write-line "NULL" cMode) (write-line ln2 cMode))
	(if (not ln3) (write-line "NULL" cMode) (write-line ln3 cMode))
	(close cMode)
	(princ)
)

(defun binMode (lst / i)
	(setq i 0)
	(while (not (= lst nil))
		(setq el (expt 2 (- (car lst) 1)))
		(setq lst (cdr lst))
		(setq i (+ i el))
	)
)

(defun c:PLSet( / df ln linArr dcl_id PreNam chk temp preset)
	(setq dcl_id (load_dialog "C:\\Users\\Ecoland\\Documents\\GitHub Files\\Ecoland-Code\\Additional-Functions Dialog.dcl"))
	(new_dialog "PLSet" dcl_id)
	(setq
		tPntOn 0
		tLblOn 0
		tBoxOn 0
		tCoordOn 0
		tCLbl 0
		df nil
		u nil
		PreNam ""
		end 0
	)
	(action_tile "f1" "(setq tPntOn 1)")
	(action_tile "f2" "(setq tLblOn 1)")
	(action_tile "f3" "(setq tBoxOn 1)")
	(action_tile "f4" "(setq tCoordOn 1)")
	(action_tile "d1" "(setq df T)")
	(action_tile "d2" "(setq df nil)")
	(action_tile "o1" "(setq tCLbl 1)")
	(action_tile "cancel" "(done_dialog)")
	(action_tile "accept"
		(strcat
		"(setq PreNam (get_tile \"e1\")) "
		"(done_dialog) "
		"(setq sum (+ tPntOn (+ tLblOn tCoordOn)))"
		"(if (= sum 0) ()
			(progn
				(setq PntOn tPntOn)
				(setq LblOn tLblOn)
				(setq BoxOn tBoxOn)
				(setq CoordOn tCoordOn)
				(setq CLbl tCLbl)
				(if (= df T)
					(progn	
						(writeToSaveFile (binMode (list 5 6 7 8 9)) (list (itoa PntOn) (itoa LblOn) (itoa BoxOn) (itoa CoordOn) (itoa CLbl)))
						(setq dPntOn PntOn)
						(setq dLblOn LblOn)
						(setq dBoxOn BoxOn)
						(setq dCoordOn CoordOn)
						(setq dCLbl CLbl)
					)
				)
			)
		)"
		)
	)
	(start_dialog)
	(unload_dialog dcl_id)
	(if (= sum 0)
		(progn
			(prompt "Invalid selection.")
			(setq end 1)
		)
	)
	(if (or (= PreNam "") (= end 1)) ()
		(progn
			(if (or (= (strcase PreNam) "C") (= (strcase PreNam) "CANCEL"))
				(prompt "\nUnavailable command name.")
				(progn
					(setq temp PreNam)
					(setq chk 0)
					(while (not (= temp ""))
						(if (= (substr temp 1 1) " ") (setq chk 1))
						(setq temp (substr temp 2 (- (strlen temp) 1)))
					)
					(if (= chk 0)
						(progn
							(setq linArr (list nil))
							(setq chk 0)
							(if (findfile "C:\\Users\\Ecoland\\Documents\\Helpful Code\\LSP Files\\Preset.lsp")
								(progn
									(setq preset (open "C:\\Users\\Ecoland\\Documents\\Helpful Code\\LSP Files\\Preset.lsp" "r"))
									(setq ln nil)
									(if (= (setq ln (read-line preset)) nil) ()
										(progn
											(setq linArr (list ln))
											(while (not (= (setq ln (read-line preset)) nil))
												(if (= (strcase (substr ln 10 (- (strlen ln) 11)) T) (strcase PreNam T)) (setq chk 1))
												(setq linArr (append linArr (list ln)))
											)
										)
									)
									(close preset)
									(setq linArr (append linArr (list nil)))
								)
							)
							(setq preset (open "C:\\Users\\Ecoland\\Documents\\Helpful Code\\LSP Files\\Preset.lsp" "w"))
							(while (not (= (car linArr) nil))
								(write-line (car linArr) preset)
								(setq linArr (cdr linArr))
							)
							(if (= chk 0)
								(progn
									(write-line (strcat "(defun c:" PreNam "()") preset)
									(write-line (strcat "	(PntNLbl " (itoa PntOn) " " (itoa LblOn) " " (itoa BoxOn) " " (itoa CoordOn) " " (itoa CLbl) ")") preset)
									(write-line "	(princ)" preset)
									(write-line ")\n" preset)
								)
								(prompt "\nThat preset name is already in use.")
							)
							(close preset)
							(load "C:\\Users\\Ecoland\\Documents\\Helpful Code\\LSP Files\\Preset.lsp")
						)
						(prompt "\nInvalid command name. Spaces are not allowed.")
					)
				)
			)
			
		)
	)
	(princ)
)

(defun c:PLFeat ( / tRC tA tPC)
	(setq dcl_id (load_dialog "C:\\Users\\Ecoland\\Documents\\GitHub Files\\Ecoland-Code\\Additional-Functions Dialog.dcl"))
	(new_dialog "PLFeat" dcl_id)
	(setq
		tRE 0
		tA 0
		tPC 0
	)
	(action_tile "f1" "(setq tRE 1)")
	(action_tile "f2" "(setq tA 1)")
	(action_tile "f3" "(setq tPC 1)")
	(action_tile "cancel" "(done_dialog)")
	(action_tile "accept"
		(strcat
		"(done_dialog)"
		"(setq elOn tRE)"
		"(setq arrow tA)"
		"(setq prntCrd tPC)"
		"(writeToSaveFile (binMode (list 10 11 12)) (list elOn arrow prntCrd))"
		)
	)
	(start_dialog)
	(unload_dialog dcl_id)
	(princ)
)

(defun c:reload()
	(load "C:\\Users\\Ecoland\\Documents\\GitHub Files\\Ecoland-Code\\Additional-Functions.lsp")
	(princ)
)

(defun c:deleteF()
	(princ)
)

(defun c:listPres( / presF ln)
	(setq presF (open "C:\\Users\\Ecoland\\Documents\\Helpful Code\\LSP Files\\Preset.lsp" "r"))
	(prompt "\nList of Presets:\n")
	(while (not (= (setq ln (read-line presF)) nil))
		(prompt (strcat "--" (substr ln 10 (- (strlen ln) 11)) "--\n"))
		(setq ln (read-line presF))
		(prompt (strcat "   -Point: " (if (= (substr ln 11 1) "1") "On" "Off") "\n"))
		(prompt (strcat "   -Label: " (if (= (substr ln 13 1) "1") "On" "Off") "\n"))
		(prompt (strcat "   -Label Border: " (if (= (substr ln 15 1) "1") "On" "Off") "\n"))
		(prompt (strcat "   -Record Coordinate: " (if (= (substr ln 17 1) "1") "On" "Off") "\n"))
		(prompt (strcat "   -Custom Label: " (if (= (substr ln 19 1) "1") "On" "Off") "\n"))
		(setq ln (read-line presF))
		(setq ln (read-line presF))
		(setq ln (read-line presF))
	)
	(close presF)
	(princ)
)

(defun c:delPres( / presF chk presNam ln linArr)
	(setq presF (open "C:\\Users\\Ecoland\\Documents\\Helpful Code\\LSP Files\\Preset.lsp" "r"))
	(setq kwrdS nil)
	(setq initS nil)
	(while (not (= (setq ln (read-line presF)) nil))
		;(print (strcase (substr ln 2 5)))
		(if (= (strcase (substr ln 2 5)) "DEFUN")
			(progn
				(setq fNm (strcase (substr ln 10 (- (strlen ln) 11))))
				(if (= initS nil)
					(setq initS fNm)
					(setq initS (strcat initS " " fNm))
				)
				(if (= kwrdS nil)
					(setq kwrdS (strcat "[" fNm))
					(setq kwrdS (strcat kwrdS "/" fNm))
				)
			)
		)
	)
	(setq initS (strcat initS " C"))
	(setq kwrdS (strcat kwrdS "/Cancel]"))
	(initget initS)
	(setq presNam (cond ((getkword (strcat "Select preset to delete " kwrdS " <Cancel>:"))) ("C")))
	(close presF)
	(if (= presNam "C") ()
		(progn
			(setq presF (open "C:\\Users\\Ecoland\\Documents\\Helpful Code\\LSP Files\\Preset.lsp" "r"))
			(setq chk 0)
			(while (not (= (setq ln (read-line presF)) nil))
				(if (= (strcase (substr ln 10 (- (strlen ln) 11)) T) (strcase presNam T))
					(setq chk 1)
				)
			)
			(close presF)
			(if (= chk 0)
				(prompt "\nThere is no preset with that name.")
				(progn
					(setq presF (open "C:\\Users\\Ecoland\\Documents\\Helpful Code\\LSP Files\\Preset.lsp" "r"))
					(setq ln (read-line presF))
					(setq linArr (list ln))
					(while (not (= (setq ln (read-line presF)) nil))
						(setq linArr (append linArr (list ln)))
					)
					(close presF)
					(setq presF (open "C:\\Users\\Ecoland\\Documents\\Helpful Code\\LSP Files\\Preset.lsp" "w"))
					(while (not (= (car linArr) nil))
						(if (= (strcase (substr (car linArr) 10 (- (strlen (car linArr)) 11)) T) (strcase presNam T))
							(progn
								(setq linArr (cddddr linArr))
								(setq linArr (cdr linArr))
							)
							(progn
								(write-line (car linArr) presF)
								(setq linArr (cdr linArr))
								(write-line (car linArr) presF)
								(setq linArr (cdr linArr))
								(write-line (car linArr) presF)
								(setq linArr (cdr linArr))
								(write-line (car linArr) presF)
								(setq linArr (cdr linArr))
								(write-line (car linArr) presF)
								(setq linArr (cdr linArr))
							)
						)
						
					)
					(close presF)
					(prompt "\nPreset deleted.")
				)
			)
		)
	)
	(princ)
)

(defun c:delAPres( / presF)
	(setq q (getYN "Delete all presets? [Yes/No]<Yes>: "))
	(if (= q 1)
		(progn
			(setq presF (open "C:\\Users\\Ecoland\\Documents\\Helpful Code\\LSP Files\\Preset.lsp" "w"))
			(close presF)
			(prompt "\nAll presets deleted.")
		)
	)
	(princ)
)

(defun c:backupPoints()
	(writeToCModes (binMode (list 1)) (list "4"))
	(startapp "C:\\Users\\Ecoland\\Documents\\Helpful Code\\Coordinate Formatter.exe")
)

(defun c:dlPt( / lNam sel q e1 e2 ss xdat1 xdat2)
	(setq lNam (entsel "Select point or label to be deleted: "))
	(setq e1 (entget (car lNam) '("Name")))
	(setq xdat1 (cdr (car (cdr (car (cdr (assoc -3 e1)))))))
	(if (= xdat1 nil) (prompt "\nInvalid selection.")
		(progn
			(setq sel (entnext))
			(setq ss (ssadd (car lNam)))
			(while (not (= sel nil))
				(setq e2 (entget sel '("Name")))
				(setq xdat2 (cdr (car (cdr (car (cdr (assoc -3 e2)))))))
				(if (= xdat1 xdat2)
					(setq ss (ssadd sel ss))
				)
				(setq sel (entnext sel))
			)
			(command "_erase" ss "")
			(prompt "Label and Point deleted.\n")
			(setq q (getYN "Continue? [Yes/No] <Yes>: "))
			(if (= q 0)
				(command "_undo" 1)
				(progn
					(writeToCModes (binMode (list 1 2 3)) (list "5" xdat1 (getvar "dwgname")))
					(startapp "C:\\Users\\Ecoland\\Documents\\Helpful Code\\Coordinate Formatter.exe")
				)
			)
		)
	)
	(princ)
)

(defun c:movPt( / lNam e1 xdat1 mPntOn mLblOn mBoxOn sel ss e2 xdat2 )
	(setq lNam (entsel "Select point or label to be moved: "))
	(setq e1 (entget (car lNam) '("Name")))
	(setq xdat1 (cdr (car (cdr (car (cdr (assoc -3 e1)))))))
	(if (= xdat1 nil) (prompt "\nInvalid selection.")
		(progn
			(setq mPntOn 0)
			(setq mLblOn 0)
			(setq mBoxOn 0)
			(setq arrow 0)
			(setq sel (entnext))
			(setq ss (ssadd (car lNam)))
			(while (not (= sel nil))
				(setq e2 (entget sel '("Name")))
				(setq xdat2 (cdr (car (cdr (car (cdr (assoc -3 e2)))))))
				(if (= xdat1 xdat2)
					(progn
						(setq ss (ssadd sel ss))
						(if (= (cdr (assoc 0 e2)) "POINT") (setq mPntOn 1))
						(if (or (= (cdr (assoc 0 e2)) "TEXT") (= (cdr (assoc 0 e2)) "MTEXT")) (setq mLblOn 1))
						(if (and (= (cdr (assoc 0 e2)) "LWPOLYLINE") (= (cdr (assoc 90 e2)) 4)) (setq mBoxOn 1))
						(if (and (= (cdr (assoc 0 e2)) "LWPOLYLINE") (= (cdr (assoc 90 e2)) 3)) (setq arrow 1))
					)
				)
				(setq sel (entnext sel))
			)
			(command "_erase" ss "")
			(setq norm 0)
			(writeToSaveFile (binMode (list 1)) (list xdat1))
			(setq sNum (atoi xdat1))
			(PntNLbl mPntOn mLblOn mBoxOn 1 0)
			(setq norm 1)
			(writeToCModes (binMode (list 1 2 3)) (list "6" xdat1 (getvar "dwgname")))
			(startapp "C:\\Users\\Ecoland\\Documents\\Helpful Code\\Coordinate Formatter.exe")
		)
	)
	(princ)
)

(defun c:chngHt( / numStr eList)
	(regapp "Name")
	(if (not bns_tcircle) (load "acettxt.lsp"))
	(setq tss (entsel "Select one object from the layer you want to change the text height: "))
	(setq nwH (getreal "\nInput new text height: "))
	(setq textH nwH)
	(prompt (strcat "\nText height: " (rtos nwH)))
	(writeToSaveFile (binMode (list 2)) (list (rtos nwH)))
	(setq q (getYN "\nWould you like a label border? [Yes/No] <Yes>: "))
	(setq tss (car tss))
	(setq lyrNm (cdr (assoc 8 (entget tss))))
	(setq ss (ssget "_A" (list '(-4 . "<AND") '(0 . "LWPOLYLINE") (cons 8 lyrNm) '(-4 . "AND>"))))
	(if (not ss) ()
		(progn
			(setq i 0)
			(while (< i (sslength ss))
				(entdel (ssname ss i))
				(setq i (1+ i))
			)
		)
	)
	(setq i 0)
	(setq ss1 (ssget "_A" (list '(-4 . "<AND") '(0 . "TEXT") (cons 8 lyrNm) '(-4 . "AND>"))))
	(if (not ss1)
		(prompt "There are no labels in this layer.")
		(progn
			(while (< i (sslength ss1))
				(setq eList (entget (ssname ss1 i)))
				(setq eList (subst (cons 40 nwH) (assoc 40 eList) eList))
				(entmod eList)
				(if (= q 1)
					(progn
						(bns_tcircle (ssadd (ssname ss1 i)) "Variable" "Rectangles" nil 0.35)
						(setq lastent (entget (entlast)))
						(setq numStr (cdr (assoc 1 eList)))
						(setq exdata (list (list -3 (list "Name" (cons 1000 numStr)))))
						(setq lastent (append lastent exdata))
						(entmod lastent)
					)
				)
				(setq i (1+ i))
			)
		)
	)
	(princ)
)

(defun c:recordElevation()
	(setq q (getYN "Record elevation? [Yes/No] <Yes>: "))
	(if (= q 1)
		(setq elOn 1)
		(setq elOn 0)
	)
	(writeToSaveFile (binMode (list 10)) (list (itoa elOn)))
	(princ)
)

(defun c:PtElev( / eList)
	(setq C T)
	(while C
		(setq pt (entsel "Select point: "))
		(setq ptN (car pt))
		(setq pt (cadr pt))
		(setq ptE (entget ptN))
		(setq el (cadddr (assoc 10 ptE)))
		(command "._text" pt textH textA (rtos el 2 3))
		(setq tE (entlast))
		(setq ss (ssadd tE))
		(repeat (setq cnt (sslength ss))
			(setq e (ssname ss (setq cnt (1- cnt))))
			(if (= (cdr (assoc 0 (entget e))) "TEXT")
				(progn
					(setq xc (cadr (assoc 10 (entget e))))
					(setq yc (caddr (assoc 10 (entget e))))
					(setq pntm1 (list xc yc))
				)
			)
		)
		(setq err (vl-catch-all-apply 'moveL (list ss pt)))
		(repeat (setq cnt (sslength ss))
			(setq e (ssname ss (setq cnt (1- cnt))))
			(if (= (cdr (assoc 0 (entget e))) "TEXT")
				(progn
					(setq xc (cadr (assoc 10 (entget e))))
					(setq yc (caddr (assoc 10 (entget e))))
					(setq pntm2 (list xc yc))
				)
			)
		)
		(if (equal pntm1 pntm2)
			(progn
				(HandErr 0 nil nil nil 2)
				(setq C nil)
			)
		)
		(setq eList (entget tE))
		(setq eList (subst (list 10 (cadr (assoc 10 eList)) (caddr (assoc 10 eList)) el) (assoc 10 eList) eList))
		(entmod eList)
	)
	(princ)
)

(defun c:ExportCoordinates() ; For research purposes (not efficient)
	(setq fil (open "C:\\Users\\Ecoland\\Documents\\Temp.txt" "w"))
	(while T
		(setq pt (getpoint "\nChoose point: "))
		(setq x (car pt))
		(setq y (cadr pt))
		(setq out (strcat (rtos x 2 8) "," (rtos y 2 8)))
		(write-line out fil)
	)
	(close fil)
	(princ)
)

(defun c:ArrowPL ( / q)
	(setq q (getYN "Label to point arrow? [Yes/No] <Yes>: "))
	(if (= q 1)
		(setq arrow 1)
		(setq arrow 0)
	)
	(writeToSaveFile (binMode (list 11)) (list (itoa arrow)))
	(princ)
)

(defun c:PrintCoord ( / q)
	(setq q (getYN "Print Coordinate? [Yes/No] <Yes>: "))
	(if (= q 1)
		(setq prntCrd 1)
		(setq prntCrd 0)
	)
	(writeToSaveFile (binMode (list 12)) (list (itoa prntCrd)))
	(princ)
)

(defun c:linePL( / eList)
	(setq c 2)
	(setq linLst '("LINE") ; "LWPOLYLINE" "POLYLINE" "SPLINE" "ARC" "CIRCLE" "ELLIPSE"))
	(setq spc (getreal "Input maximum differnece between points: "))
	(prompt "\nSelect lines which you want points and labels on: \n")
	(setq eList (list))
	(while (= c 2)
		(setq temp (vl-catch-all-apply 'entsel (list "\nChoose line or press \"esc\" when done: ")))
		(if (vl-catch-all-error-p temp)
			(progn
				(if (= (vl-catch-all-error-message temp) "Function cancelled")
					(progn
						(prompt "\nLine selection finished.")
						(setq c 1)
					)
					(progn
						(prompt (strcat "\nError: " (vl-catch-all-error-message numStr) "."))
						(setq c 0)
					)
				)
			)
			(progn
				(setq temp (car temp))
				(if (/= temp nil)
					(if (/= (member (cdr (assoc 0 (entget temp))) linLst) nil)
						(if (= (member temp eList) nil)
							(setq eList (append eList (list temp)))
							(prompt "\nLine already selected.")
						)
						(prompt "\nInvalid selection.")
					)
					(prompt "\nNo object selected.")
				)
			)
		)
	)
	(princ)
)

(prompt "\nAdditional functions loaded.")
(princ)
